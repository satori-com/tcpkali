TcpkaliOrchestration DEFINITIONS AUTOMATIC TAGS ::= BEGIN

    TcpkaliMessage ::= CHOICE {
        increaseRatePercent   IncreaseRatePercent,
        decreaseRatePercent   DecreaseRatePercent,
        setRate               SetRate
    }

    IncreaseRatePercent ::= INTEGER(1..100)
    DecreaseRatePercent ::= INTEGER(1..100)
    SetRate             ::= INTEGER

END
