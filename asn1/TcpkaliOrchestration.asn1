TcpkaliOrchestration DEFINITIONS AUTOMATIC TAGS EXTENSIBILITY IMPLIED ::= BEGIN

    TcpkaliMessage ::= CHOICE {
        start                 Start,
        stop                  Stop,
        increaseRatePercent   IncreaseRatePercent,
        decreaseRatePercent   DecreaseRatePercent,
        setRate               SetRate,
        currentRate           CurrentRate
    }

    Start ::= SEQUENCE {
        target                         URL OPTIONAL,
        nagle                          BOOLEAN OPTIONAL,
        rcvbuf                         PositiveInteger OPTIONAL,
        sndbuf                         PositiveInteger OPTIONAL,
        writeCombine                   BOOLEAN OPTIONAL,
        workers                        PositiveInteger OPTIONAL,
        ws                             BOOLEAN OPTIONAL,
        ssl                            BOOLEAN OPTIONAL,
        sslCert                        PrintableString OPTIONAL,
        sslKey                         PrintableString OPTIONAL,
        header                         PrintableString OPTIONAL,
        connections                    PositiveInteger OPTIONAL,
        connectRate                    PositiveReal OPTIONAL,
        connectTimeout                 PositiveReal OPTIONAL,
        channelLifetime                PositiveReal OPTIONAL,
        channelBandwidthUpstream       PositiveReal OPTIONAL,
        channelBandwidthDownstream     PositiveReal OPTIONAL,
        listenPort                     TcpPort OPTIONAL,
        listenMode                     ENUMERATED {silent (0) , active (1)} OPTIONAL,
        duration                       PositiveReal OPTIONAL,
        delaySend                      PositiveReal OPTIONAL,
        firstMessage                   OCTET STRING OPTIONAL,
        message                        OCTET STRING OPTIONAL,
        messageFile                    PrintableString OPTIONAL,
        messageRate                    PositiveReal OPTIONAL,
        messageStop                    OCTET STRING OPTIONAL,
        latencyConnect                 BOOLEAN OPTIONAL,
        latencyFirstByte               BOOLEAN OPTIONAL,
        latencyMarker                  PrintableString OPTIONAL,
        latencyMarkerSkip              PositiveInteger OPTIONAL,
        latencyPercentiles             PrintableString OPTIONAL,
        messageMarker                  BOOLEAN OPTIONAL,
        statsd                         BOOLEAN OPTIONAL,
        statsdHost                     PrintableString OPTIONAL,
        statsdPort                     TcpPort OPTIONAL,
        statsdNamespace                PrintableString OPTIONAL,
        statsdLatencyWindow            PositiveInteger OPTIONAL
    }

    Stop ::= SEQUENCE {
    }

    TcpPort ::= INTEGER (1..65535)

    IncreaseRatePercent ::= INTEGER (0..100)
    DecreaseRatePercent ::= INTEGER (0..100)
    SetRate             ::= PositiveReal
    CurrentRate         ::= SEQUENCE {
        valueBase ENUMERATED {unlimited(0), bytesPerSecond(1), messagesPerSecond(2)},
        value NonNegativeReal
    }

    PositiveInteger ::= INTEGER (1..MAX)

    NonNegativeReal ::= REAL (0|WITH COMPONENTS {
                    base (2), exponent (-10..104), mantissa (0..16777215) })

    PositiveReal ::= REAL (WITH COMPONENTS {
                    base (2), exponent (-10..104), mantissa (0..16777215) })

    URL ::= PrintableString

END
